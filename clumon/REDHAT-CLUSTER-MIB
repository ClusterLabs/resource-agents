REDHAT-CLUSTER-MIB DEFINITIONS ::= BEGIN


IMPORTS
	RedHat					FROM REDHAT-MIB
	MODULE-IDENTITY, OBJECT-TYPE, Integer32	FROM SNMPv2-SMI;


RedHatCluster MODULE-IDENTITY
    LAST-UPDATED "200512060000Z"            -- Dec 06 2005, midnight
    ORGANIZATION "Red Hat, Inc (www.redhat.com)"
    CONTACT-INFO "postal:   Red Hat, Inc
		   	    1801 Varsity Drive
			    Raleigh, North Carolina 27606
			    USA
		  
		  email:    customerservice@redhat.com
                 "
    DESCRIPTION  "Red Hat Cluster Suite MIB
                 "
    REVISION     "200512060000Z"            -- Dec 06 2005, midnight
    DESCRIPTION  "MIB version 1
		 "
    ::= { RedHat 8 }



rhcMIBInfo		OBJECT IDENTIFIER ::= { RedHatCluster 1 }
rhcCluster		OBJECT IDENTIFIER ::= { RedHatCluster 2 }
rhcTables		OBJECT IDENTIFIER ::= { RedHatCluster 3 }
	



--  #####  MIB info #####

rhcMIBVersion OBJECT-TYPE
	SYNTAX      Integer32
	MAX-ACCESS  read-only
	STATUS      current
	DESCRIPTION
	"Version of Red Hat Cluster MIB
	"
	::= { rhcMIBInfo 1 }



--  #####  Cluster  #####  --

rhcClusterName OBJECT-TYPE
	SYNTAX      OCTET STRING
	MAX-ACCESS  read-only
	STATUS      current
	DESCRIPTION
	"Cluster name"
	::= { rhcCluster 1 }


rhcClusterStatusCode OBJECT-TYPE
	SYNTAX      Integer32
	MAX-ACCESS  read-only
	STATUS      current
	DESCRIPTION
	"Cluster status code.
	ORed values:
		1	All services and nodes functional
		2	Some services failed
		4	Some services not running
		8	Some nodes unavailable
		16	Not quorate
		32	Cluster stopped
	"
	::= { rhcCluster 2 }

rhcClusterStatusDesc OBJECT-TYPE
	SYNTAX      OCTET STRING
	MAX-ACCESS  read-only
	STATUS      current
	DESCRIPTION
	"Cluster status description"
	::= { rhcCluster 3 }


rhcClusterVotesNeededForQuorum OBJECT-TYPE
	SYNTAX      Integer32
	MAX-ACCESS  read-only
	STATUS      current
	DESCRIPTION
	"Minimum number of votes required for quorum. 
	If cluster is not quorate, all services are stopped."
	::= { rhcCluster 4 }

rhcClusterVotes OBJECT-TYPE
	SYNTAX      Integer32
	MAX-ACCESS  read-only
	STATUS      current
	DESCRIPTION
	"Current number of votes"
	::= { rhcCluster 5 }

rhcClusterQuorate OBJECT-TYPE
	SYNTAX      Integer32
	MAX-ACCESS  read-only
	STATUS      current
	DESCRIPTION
	"1 if cluster is quorate, 0 otherwise"
	::= { rhcCluster 6 }


rhcClusterNodesNum OBJECT-TYPE
	SYNTAX      Integer32
	MAX-ACCESS  read-only
	STATUS      current
	DESCRIPTION
	"Number of nodes configured to participate in cluster"
	::= { rhcCluster 7 }

rhcClusterNodesNames OBJECT-TYPE
	SYNTAX      OCTET STRING
	MAX-ACCESS  read-only
	STATUS      current
	DESCRIPTION
	"Names of nodes configured to participate in cluster"
	::= { rhcCluster 8 }

rhcClusterAvailNodesNum OBJECT-TYPE
	SYNTAX      Integer32
	MAX-ACCESS  read-only
	STATUS      current
	DESCRIPTION
	"Number of nodes currently participating in cluster"
	::= { rhcCluster 9 }

rhcClusterAvailNodesNames OBJECT-TYPE
	SYNTAX      OCTET STRING
	MAX-ACCESS  read-only
	STATUS      current
	DESCRIPTION
	"Names of nodes currently participating in cluster"
	::= { rhcCluster 10 }

rhcClusterUnavailNodesNum OBJECT-TYPE
	SYNTAX      Integer32
	MAX-ACCESS  read-only
	STATUS      current
	DESCRIPTION
	"Number of nodes currently NOT participating in cluster"
	::= { rhcCluster 11 }

rhcClusterUnavailNodesNames OBJECT-TYPE
	SYNTAX      OCTET STRING
	MAX-ACCESS  read-only
	STATUS      current
	DESCRIPTION
	"Names of nodes currently NOT participating in cluster"
	::= { rhcCluster 12 }


rhcClusterServicesNum OBJECT-TYPE
	SYNTAX      Integer32
	MAX-ACCESS  read-only
	STATUS      current
	DESCRIPTION
	"Number of configured services"
	::= { rhcCluster 13 }

rhcClusterServicesNames OBJECT-TYPE
	SYNTAX      OCTET STRING
	MAX-ACCESS  read-only
	STATUS      current
	DESCRIPTION
	"Names of configured services"
	::= { rhcCluster 14 }

rhcClusterRunningServicesNum OBJECT-TYPE
	SYNTAX      Integer32
	MAX-ACCESS  read-only
	STATUS      current
	DESCRIPTION
	"Number of running services"
	::= { rhcCluster 15 }

rhcClusterRunningServicesNames OBJECT-TYPE
	SYNTAX      OCTET STRING
	MAX-ACCESS  read-only
	STATUS      current
	DESCRIPTION
	"Names of running services"
	::= { rhcCluster 16 }

rhcClusterStoppedServicesNum OBJECT-TYPE
	SYNTAX      Integer32
	MAX-ACCESS  read-only
	STATUS      current
	DESCRIPTION
	"Number of stopped services"
	::= { rhcCluster 17 }

rhcClusterStoppedServicesNames OBJECT-TYPE
	SYNTAX      OCTET STRING
	MAX-ACCESS  read-only
	STATUS      current
	DESCRIPTION
	"Names of stopped services"
	::= { rhcCluster 18 }

rhcClusterFailedServicesNum OBJECT-TYPE
	SYNTAX      Integer32
	MAX-ACCESS  read-only
	STATUS      current
	DESCRIPTION
	"Number of failed services"
	::= { rhcCluster 19 }

rhcClusterFailedServicesNames OBJECT-TYPE
	SYNTAX      OCTET STRING
	MAX-ACCESS  read-only
	STATUS      current
	DESCRIPTION
	"Names of failed services"
	::= { rhcCluster 20 }



--  ##### nodes #####  --


rhcNodesTable OBJECT-TYPE
	SYNTAX      SEQUENCE OF RhcNodeEntry
	MAX-ACCESS  not-accessible
	STATUS      current
	DESCRIPTION
        "Table of cluster nodes"
	::= { rhcTables 1 }

rhcNodeEntry OBJECT-TYPE
	SYNTAX      RchNodeEntry
	MAX-ACCESS  not-accessible
	STATUS      current
	DESCRIPTION
        "Cluster node"
	INDEX   { rhcNodeName }
	::= { rhcNodesTable 1 }

RhcNodeEntry ::= SEQUENCE {
	rhcNodeName			OCTET STRING,
	rhcNodeStatusCode		Integer32,
	rhcNodeStatusDesc    		OCTET STRING,
	rhcNodeRunningServicesNum	Integer32,
	rhcNodeRunningServicesNames	OCTET STRING
}

rhcNodeName OBJECT-TYPE
	SYNTAX      OCTET STRING
	MAX-ACCESS  read-only
	STATUS      current
	DESCRIPTION
	"Node name"
	::= { rhcNodeEntry 1 }


rhcNodeStatusCode OBJECT-TYPE
	SYNTAX      Integer32
	MAX-ACCESS  read-only
	STATUS      current
	DESCRIPTION
	"Node status code.
	Values:
		0	Participating in cluster
		1	Running, but not participating in cluster
		2	Not running
	"
	::= { rhcNodeEntry 2 }

rhcNodeStatusDesc OBJECT-TYPE
	SYNTAX      OCTET STRING
	MAX-ACCESS  read-only
	STATUS      current
	DESCRIPTION
	"Node status description"
	::= { rhcNodeEntry 3 }


rhcNodeRunningServicesNum OBJECT-TYPE
	SYNTAX      Integer32
	MAX-ACCESS  read-only
	STATUS      current
	DESCRIPTION
	"Number of services running on node"
	::= { rhcNodeEntry 4 }

rhcNodeRunningServicesNames OBJECT-TYPE
	SYNTAX      OCTET STRING
	MAX-ACCESS  read-only
	STATUS      current
	DESCRIPTION
	"Names of services running on node"
	::= { rhcNodeEntry 5 }



--  ##### services #####  --


rhcServicesTable OBJECT-TYPE
	SYNTAX      SEQUENCE OF RhcServiceEntry
	MAX-ACCESS  not-accessible
	STATUS      current
	DESCRIPTION
        "Table of cluster services"
	::= { rhcTables 2 }

rhcServiceEntry OBJECT-TYPE
	SYNTAX      RchServiceEntry
	MAX-ACCESS  not-accessible
	STATUS      current
	DESCRIPTION
	"Cluster service"
	INDEX   { rhcServiceName }
	::= { rhcServicesTable 1 }

RhcServiceEntry ::= SEQUENCE {
	rhcServiceName		OCTET STRING,
	rhcServiceStatusCode	Integer32,
	rhcServiceStatusDesc	OCTET STRING,
	rhcServiceStartMode	OCTET STRING,
	rhcServiceRunningOnNode	OCTET STRING
}

rhcServiceName OBJECT-TYPE
	SYNTAX      OCTET STRING
	MAX-ACCESS  read-only
	STATUS      current
	DESCRIPTION
	"Service name"
	::= { rhcServiceEntry 1 }

rhcServiceStatusCode OBJECT-TYPE
	SYNTAX      Integer32
	MAX-ACCESS  read-only
	STATUS      current
	DESCRIPTION
	"Service status code.
	Codes:
		0	running
		1	stopped
		2	failed
	"
	::= { rhcServiceEntry 2 }

rhcServiceStatusDesc OBJECT-TYPE
	SYNTAX      OCTET STRING
	MAX-ACCESS  read-only
	STATUS      current
	DESCRIPTION
	"Dervice status description"
	::= { rhcServiceEntry 3 }

rhcServiceStartMode OBJECT-TYPE
	SYNTAX      OCTET STRING
	MAX-ACCESS  read-only
	STATUS      current
	DESCRIPTION
	"Service start mode, automatic or manual"
	::= { rhcServiceEntry 4 }

rhcServiceRunningOnNode OBJECT-TYPE
	SYNTAX      OCTET STRING
	MAX-ACCESS  read-only
	STATUS      current
	DESCRIPTION
	"Name of node the service runs on"
	::= { rhcServiceEntry 5 }




END
